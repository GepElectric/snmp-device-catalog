-- File HOPF_FG6890G01.MIB
-- Defines HOPF-FG6890G01-MIB (hopf Eelektronik GmbH proprietary MIB for FG6890G01 DIN rail module time servers)

-- HOPF-FG6890G01-MIB { iso(1) org(3) dod(6) internet(1) private(4)
--               enterprises(1) hopf(12527) }

HOPF-FG6890G01-MIB DEFINITIONS ::= BEGIN

--  (c) 2005-2021 by hopf Elektronik GmbH and RDCS Informationstechnologie GmbH

--  FILENAME        : HOPF_FG6890G01.MIB
--  AUTHOR          : HOPF/POSCH
--  DATE OF CREATION: 2022-06-08

--  DESCRIPTION:
--  Definition of the proprietary MIB for FG6890G01 DIN rail module time servers.
--  The NTP part of this MIB is partly implemented as proposed in the 
--  Technical Report No. 98-09 by Adarshpal S. Sethi and David Mills.

--  DOCUMENTATION OF CHANGES:

--  NUMBER  | AUTHOR |    DATE    | DESCRIPTION
--  --------+--------+------------+--------------------------------------------------------------
--  @00001  |  POM   | 2022-06-08 | Correction of systemTime OID
--  --------+--------+------------+--------------------------------------------------------------

IMPORTS
    MODULE-IDENTITY, OBJECT-TYPE,
    enterprises, Integer32, NOTIFICATION-TYPE
        FROM SNMPv2-SMI
    TEXTUAL-CONVENTION, DisplayString
        FROM SNMPv2-TC;

--
-- The position of the 6890 DIN rail time server within the enterprise
--
hopfFG6890G01 MODULE-IDENTITY
     LAST-UPDATED "202206080000Z"
     ORGANIZATION "hopf Elektronik GmbH"
     CONTACT-INFO
        "Markus POSCH
         hopf Elektronik GmbH
         Nottebohmstrasse 41
         58511 Luedenscheid
         Germany
         Tel: +49-2351-938686
         eMail: support@hopf.com

         Wolfgang KANOVSKY
         RDCS Informationstechnologie GmbH
         Embelgasse 66/10-11
         1050 Vienna
         Austria
         Tel: +43-1-5455077-0
         eMail: support@rdcs.eu"
     DESCRIPTION
        "This MIB module defines a MIB which provides mechanisms to
         monitor and control the FG6890G01 DIN rail module time server."
     REVISION "202206080000Z"
     DESCRIPTION
        "Syntax error corrections."
     ::= { hopf 51 }

--
-- The position of the enterprise within the OID hierarchy of this MIB:
--
hopf OBJECT IDENTIFIER ::= { enterprises 12527 }

--
-- Definitions for the general device CONFIGURATION subsystem:
--
general OBJECT IDENTIFIER ::= { hopfFG6890G01 1 }

deviceType OBJECT-TYPE
    SYNTAX      DisplayString (SIZE (0..9))
    MAX-ACCESS  read-only
    STATUS      current
    DESCRIPTION "string which describes the device type, valid values are:
                 6890 --> NTP DIN rail time server with one ethernet
                               interface 10/100MBit autosensing"
    ::= { general 1 }

layoutVersion OBJECT-TYPE
    SYNTAX      DisplayString (SIZE (0..1))
    MAX-ACCESS  read-only
    STATUS      current
    DESCRIPTION "Character which describes the current layout version of
                 the expansion card hardware. Characters for versions are
                 in upper case notation and begin with version 'A'"
    ::= { general 2 }

serialNumber OBJECT-TYPE
    SYNTAX      DisplayString (SIZE (0..32))
    MAX-ACCESS  read-only
    STATUS      current
    DESCRIPTION "serial number of the expansion card, unique
                 to each individual device"
    ::= { general 3 }

firmwareVersion OBJECT-TYPE
    SYNTAX      DisplayString (SIZE (0..5))
    MAX-ACCESS  read-only
    STATUS      current
    DESCRIPTION "string which describes the current version of
                 the expansion card software for the embedded sub-system.
                 version numbers are two digits for the major version and
                 two digtis for the minor version devided by a dot (e.g. 01.00)"
    ::= { general 4 }

firmwareDate OBJECT-TYPE
    SYNTAX      OCTET STRING
    MAX-ACCESS  read-only
    STATUS      current
    DESCRIPTION "date when the firmware version has been released"
    ::= { general 5 }

systemTime OBJECT-TYPE
    SYNTAX      OCTET STRING
    MAX-ACCESS  read-only
    STATUS      current
    DESCRIPTION "Current UTC date and time on the 6890 DIN rail time server."
    ::= { general 10 }

--
-- Definitions for the NTP subsystem:
--
ntp OBJECT IDENTIFIER ::= { hopfFG6890G01 2 }

ntpSystem OBJECT IDENTIFIER ::= { ntp 1 }
ntpPeer  OBJECT IDENTIFIER ::= { ntp 2 }

--
-- Textual conventions for the NTP subset
--
NTPTimeStamp ::= TEXTUAL-CONVENTION
    DISPLAY-HINT "2d-1d-1d,1d:1d:1d.2d"
    STATUS       current
    DESCRIPTION
            "A date-time specification.

            field  octets  contents                  range
            -----  ------  --------                  -----
              1      1-2   year*                     0..65536
              2       3    month                     1..12
              3       4    day                       1..31
              4       5    hour                      0..23
              5       6    minutes                   0..59
              6       7    seconds                   0..60
                           (use 60 for leap-second)
              7      8-9   milli-seconds*            0..999

            * Notes:
            - the value of year and milli-seconds is in network-byte order

            For example, Tuesday May 26, 1992 at 1:30:15 PM would be
            displayed as: 1992-5-26,13:30:15.0"
    SYNTAX OCTET STRING (SIZE (9))

NTPLeapIndicator ::= TEXTUAL-CONVENTION
    STATUS      current
    DESCRIPTION "two-bit code warning of an impending leap
                 second to be inserted in the NTP timescale."
    SYNTAX INTEGER {
        noWarning(0),
        addSecond(1),
        subtractSecond(2),
        alarm(3)
    }

ntpAccuracy  OBJECT-TYPE
    SYNTAX      INTEGER { low(0), medium(1), high(2) }
    MAX-ACCESS  read-only
    STATUS      current
    DESCRIPTION "calculated value which takes into account the following parameters:
                 - syncSourceTimeSyncState
                 - ntpSysRootDelay
                 - ntpSysRootDispersion
                 - ntpSysStability"
    ::= { ntp 3 }
	
ntpRunning  OBJECT-TYPE
    SYNTAX      INTEGER { shutdown(0), running(1) }
    MAX-ACCESS  read-only
    STATUS      current
    DESCRIPTION "indicates the operating status of the ntp timeservice"
    ::= { ntp 4 }

--
-- NTP System Group
--
ntpSysLeap OBJECT-TYPE
    SYNTAX      NTPLeapIndicator
    MAX-ACCESS  read-only
    STATUS      current
    DESCRIPTION "two-bit code warning of an impending leap
                 second to be inserted in the NTP timescale."
    ::= { ntpSystem 1 }

ntpSysStratum OBJECT-TYPE
    SYNTAX      Integer32 (0..16)
    MAX-ACCESS  read-only
    STATUS      current
    DESCRIPTION "indicating the stratum of the local clock.
                 0    --> unspecified
                 1    --> primary reference (e.g.,, calibrated atomic clock,
                          radio clock)
                 2-15 --> secondary reference (via NTP)
                 16   --> invalid"
    ::= { ntpSystem 2 }

ntpSysPrecision OBJECT-TYPE
    SYNTAX      Integer32
    MAX-ACCESS  read-only
    STATUS      current
    DESCRIPTION "signed integer indicating the precision
                 of the various clocks, in seconds to the nearest power
                 of two."
    ::= { ntpSystem 3 }

ntpSysRootDelay OBJECT-TYPE
    SYNTAX      OCTET STRING
    MAX-ACCESS  read-only
    STATUS      current
    DESCRIPTION "the total roundtrip delay to the primary
                 reference source at the root of the synchronization
                 subnet, in seconds"
    ::= { ntpSystem 4 }

ntpSysRootDispersion OBJECT-TYPE
    SYNTAX      OCTET STRING
    MAX-ACCESS  read-only
    STATUS      current
    DESCRIPTION "the maximum error relative to the primary
                 reference source at the root of the synchronization
                 subnet, in seconds. Only positive values greater
                 than zero are possible"
    ::= { ntpSystem 5 }

ntpSysJitter OBJECT-TYPE
    SYNTAX      OCTET STRING
    MAX-ACCESS  read-only
    STATUS      current
    DESCRIPTION "the jitter value of the NTP system in seconds"
    ::= { ntpSystem 6 }

ntpSysStability OBJECT-TYPE
    SYNTAX      OCTET STRING
    MAX-ACCESS  read-only
    STATUS      current
    DESCRIPTION "NTP system stability in ppm"
    ::= { ntpSystem 7 }

ntpSysRefId OBJECT-TYPE
    SYNTAX      OCTET STRING
    MAX-ACCESS  read-only
    STATUS      current
    DESCRIPTION "the particular reference clock. In the case of
                 stratum 0 (unspecified) or stratum 1 (primary reference
                 source), this is a four-octet, left-justified,zero-padded
                 ASCII string.In the case of stratum 2 and greater (secondary
                 reference) this is the four-octet Internet address of the
                 peer selected for synchronization."
    ::= { ntpSystem 8 }

ntpSysRefTime OBJECT-TYPE
    SYNTAX      NTPTimeStamp
    MAX-ACCESS  read-only
    STATUS      current
    DESCRIPTION "the local time when the local clock was last
                 updated. If the local clock has never been synchronized,
                 the value is zero."
    ::= { ntpSystem 9 }

ntpSysPeer OBJECT-TYPE
    SYNTAX      OCTET STRING
    MAX-ACCESS  read-only
    STATUS      current
    DESCRIPTION "the name of the current system peer used by ntp"
    ::= { ntpSystem 10 }

ntpKernelInfoMaxError OBJECT-TYPE
    SYNTAX      OCTET STRING
    MAX-ACCESS  read-only
    STATUS      current
    DESCRIPTION "maximum error in seconds from kernel information."
    ::= { ntpSystem 11 }

ntpKernelInfoEstError OBJECT-TYPE
    SYNTAX      OCTET STRING
    MAX-ACCESS  read-only
    STATUS      current
    DESCRIPTION "estimated error in seconds from kernel information."
    ::= { ntpSystem 12 }

--
-- NTP Peers Group
--

ntpPeerName OBJECT-TYPE
    SYNTAX      OCTET STRING
    MAX-ACCESS  read-only
    STATUS      current
    DESCRIPTION "peer identification name"
    ::= { ntpPeer 1 }

ntpPeerRefId OBJECT-TYPE
    SYNTAX      OCTET STRING
    MAX-ACCESS  read-only
    STATUS      current
    DESCRIPTION "peer reference identification number"
    ::= { ntpPeer 2 }

ntpPeerStratum OBJECT-TYPE
    SYNTAX      INTEGER
    MAX-ACCESS  read-only
    STATUS      current
    DESCRIPTION "the current stratum value of the peer"
    ::= { ntpPeer 3 }

ntpPeerReachability OBJECT-TYPE
    SYNTAX INTEGER
    MAX-ACCESS read-only
    STATUS current
    DESCRIPTION "indicates the reachability of the peer"
    ::= { ntpPeer 4 }
	
ntpPeerDelay OBJECT-TYPE
    SYNTAX OCTET STRING
    MAX-ACCESS read-only
    STATUS current
    DESCRIPTION "indicates the time delay towards the peer"
    ::= { ntpPeer 5 }
	
ntpPeerOffset OBJECT-TYPE
    SYNTAX OCTET STRING
    MAX-ACCESS read-only
    STATUS current
    DESCRIPTION "indicates the time offset to the peer"
    ::= { ntpPeer 6 }
	
ntpPeerDispersion OBJECT-TYPE
    SYNTAX OCTET STRING
    MAX-ACCESS read-only
    STATUS current
    DESCRIPTION "indicates the time dispersion to the peer"
    ::= { ntpPeer 7 }

--
-- Definitions for the states of the synchronization module
--
syncSource OBJECT IDENTIFIER ::= { hopfFG6890G01 3 }

syncSourceTimeLocal OBJECT-TYPE
    SYNTAX      OCTET STRING
    MAX-ACCESS  read-only
    STATUS      current
    DESCRIPTION "current date and time with local time base with
                 regard to time zone and daylight saving time configurations
                 of the sync module"
    ::= { syncSource 1 }

syncSourceTimeDST OBJECT-TYPE
    SYNTAX      INTEGER { off(0), on(1) }
    MAX-ACCESS  read-only
    STATUS      current
    DESCRIPTION "indicator for daylight saving time of sync module"
    ::= { syncSource 2 }

syncSourceTimeDSTChange OBJECT-TYPE
    SYNTAX      INTEGER { off(0), on(1) }
    MAX-ACCESS  read-only
    STATUS      current
    DESCRIPTION "indicator of the sync module for the announcement of a
                 daylight saving time change either from standard time to daylight
                 saving time or vice versa. the announcement is switched on one
                 hour before the actual change."
    ::= { syncSource 3 }

syncSourceTimeLEAP OBJECT-TYPE
    SYNTAX      INTEGER { off(0), on(1) }
    MAX-ACCESS  read-only
    STATUS      current
    DESCRIPTION "indicator of the sync module for the announcement of the
                 insertion of a leap second into the current time scale.
                 the announcement is switched on one hour before the actual
                 insertion of the leap second occurs."
    ::= { syncSource 4 }

syncSourceTimeSyncStatus OBJECT-TYPE
    SYNTAX      DisplayString (SIZE (0..7))
    MAX-ACCESS  read-only
    STATUS      current
    DESCRIPTION "synchronisation status of the sync module as string representation:
                 'Init' --> Not initialized
				 'Crystal' --> Crystal mode
				 'Sync-Lock' --> Locked to sync source"
    ::= { syncSource 5 }

syncSourceTimeSyncStatusInt OBJECT-TYPE
    SYNTAX      Integer32
    MAX-ACCESS  read-only
    STATUS      current
    DESCRIPTION "synchronisation status of the sync module as integer representation:
                 0 --> Not initialized
				 1 --> Quartz mode
				 2 --> Locked to sync source"
    ::= { syncSource 6 }

syncSourceTimeSyncAccuracy OBJECT-TYPE
    SYNTAX      DisplayString (SIZE (0..16))
    MAX-ACCESS  read-only
    STATUS      current
    DESCRIPTION "synchronisation accuracy of the sync module"
    ::= { syncSource 7 }

--
-- Definitions for gnss synchronization source reception:
--
hopfGnss OBJECT IDENTIFIER ::= { syncSource 101 }

hopfGnssReceptionMode OBJECT-TYPE
    SYNTAX      INTEGER (0..1)
    MAX-ACCESS  read-only
    STATUS      current
    DESCRIPTION "The reception mode of the GNSS receiver:
                 0 --> Stationary Mode (Position Fixed)
                 1 --> Automotive Mode (3D)"
    ::= { hopfGnss 1 }

hopfGnssSource1 OBJECT-TYPE
    SYNTAX      INTEGER (0..1)
    MAX-ACCESS  read-only
    STATUS      current
    DESCRIPTION "GNSS source 1:
                 0 --> NONE
                 1 --> GPS
                 2 --> GLONASS
                 3 --> GALILEO
                 4 --> BEIDOU"
    ::= { hopfGnss 12 }

hopfGnssSource2 OBJECT-TYPE
    SYNTAX      INTEGER (0..1)
    MAX-ACCESS  read-only
    STATUS      current
    DESCRIPTION "GNSS source 2:
                 0 --> NONE
                 1 --> GPS
                 2 --> GLONASS
                 3 --> GALILEO
                 1 --> BEIDOU"
    ::= { hopfGnss 13 }

hopfGnssSource3 OBJECT-TYPE
    SYNTAX      INTEGER (0..1)
    MAX-ACCESS  read-only
    STATUS      current
    DESCRIPTION "GNSS source 3:
                 0 --> NONE
                 1 --> GPS
                 2 --> GLONASS
                 3 --> GALILEO
                 1 --> BEIDOU"
    ::= { hopfGnss 14 }

hopfGnssSatInViewNumber OBJECT-TYPE
    SYNTAX      INTEGER (0..99)
    MAX-ACCESS  read-only
    STATUS      current
    DESCRIPTION "The number of satellites in view."
    ::= { hopfGnss 2 }

hopfGnssSatTrackedNumber OBJECT-TYPE
    SYNTAX      INTEGER (0..16)
    MAX-ACCESS  read-only
    STATUS      current
    DESCRIPTION "The number of actually tracked satellites in hopfGnssSatVarTable."
    ::= { hopfGnss 3 }

hopfGnssAGCMonitor OBJECT-TYPE
    SYNTAX      OCTET STRING
    MAX-ACCESS  read-only
    STATUS      current
    DESCRIPTION "Automatic Gain Control value in percent."
    ::= { hopfGnss 4 }

hopfGnssNoiseLevel OBJECT-TYPE
    SYNTAX      INTEGER (0..200)
    MAX-ACCESS  read-only
    STATUS      current
    DESCRIPTION "GNSS Core Noise Level value."
    ::= { hopfGnss 5 }

hopfGnssJamming OBJECT-TYPE
    SYNTAX      OCTET STRING
    MAX-ACCESS  read-only
    STATUS      current
    DESCRIPTION "CW Jamming indicator in percent."
    ::= { hopfGnss 6 }

hopfGnssJammingStatus OBJECT-TYPE
    SYNTAX      INTEGER (0..3)
    MAX-ACCESS  read-only
    STATUS      current
    DESCRIPTION "Jamming Status:
                 0 --> feature disabled
                 1 --> ok
                 2 --> warning
                 3 --> critical"
    ::= { hopfGnss 7 }

hopfGnssPDOP OBJECT-TYPE
    SYNTAX      OCTET STRING
    MAX-ACCESS  read-only
    STATUS      current
    DESCRIPTION "PDOP value."
    ::= { hopfGnss 8 }

hopfGnssSatVarTable OBJECT-TYPE
    SYNTAX      SEQUENCE OF HopfGnssSatVarEntry
    MAX-ACCESS  not-accessible
    STATUS      current
    DESCRIPTION ""
    ::= { hopfGnss 9 }

hopfGnssSatVarEntry OBJECT-TYPE
    SYNTAX      HopfGnssSatVarEntry
    MAX-ACCESS  not-accessible
    STATUS      current
    DESCRIPTION ""
    INDEX       { hopfGnssSatId }
    ::= { hopfGnssSatVarTable 1 }

HopfGnssSatVarEntry ::= SEQUENCE {
    hopfGnssSatId        OCTET STRING,
    hopfGnssSatQuality   INTEGER
    }

hopfGnssSatId OBJECT-TYPE
    SYNTAX      OCTET STRING (SIZE(0..256))
    MAX-ACCESS  read-only
    STATUS      current
    DESCRIPTION "identification of the tracked satellite."
    ::= { hopfGnssSatVarEntry 1 }

hopfGnssSatQuality OBJECT-TYPE
    SYNTAX      INTEGER (0..108)
    MAX-ACCESS  read-only
    STATUS      current
    DESCRIPTION "reception quality of the tracked satellite:
                 0  -  30: bad
                 31 -  45: sufficient
                 46 - 108: excellent"
    ::= { hopfGnssSatVarEntry 2 }

hopfGnssPosition OBJECT IDENTIFIER ::= { hopfGnss 10 }

hopfGnssPosLongitude OBJECT IDENTIFIER ::= { hopfGnssPosition 1 }

hopfGnssPosLongDeg OBJECT-TYPE
    SYNTAX      INTEGER (0..180)
    MAX-ACCESS  read-only
    STATUS      current
    DESCRIPTION "longitude degree value of GNSS position"
    ::= { hopfGnssPosLongitude 1 }

hopfGnssPosLongMin OBJECT-TYPE
    SYNTAX      INTEGER (0..59)
    MAX-ACCESS  read-only
    STATUS      current
    DESCRIPTION "longitude minute value of GNSS position"
    ::= { hopfGnssPosLongitude 2 }

hopfGnssPosLongSec OBJECT-TYPE
    SYNTAX      INTEGER (0..599999)
    MAX-ACCESS  read-only
    STATUS      current
    DESCRIPTION "longitude milliseconds value of GNSS position"
    ::= { hopfGnssPosLongitude 3 }

hopfGnssPosLongDir OBJECT-TYPE
    SYNTAX      INTEGER { west(0), east(1) }
    MAX-ACCESS  read-only
    STATUS      current
    DESCRIPTION "longitude direction from prime meridian"
    ::= { hopfGnssPosLongitude 4 }

hopfGnssPosLatitude OBJECT IDENTIFIER ::= { hopfGnssPosition 2 }

hopfGnssPosLatDeg OBJECT-TYPE
    SYNTAX      INTEGER (0..90)
    MAX-ACCESS  read-only
    STATUS      current
    DESCRIPTION "latitude degree value of GNSS position"
    ::= { hopfGnssPosLatitude 1 }

hopfGnssPosLatMin OBJECT-TYPE
    SYNTAX      INTEGER (0..59)
    MAX-ACCESS  read-only
    STATUS      current
    DESCRIPTION "latitude minute value of GNSS position"
    ::= { hopfGnssPosLatitude 2 }

hopfGnssPosLatSec OBJECT-TYPE
    SYNTAX      INTEGER (0..599999)
    MAX-ACCESS  read-only
    STATUS      current
    DESCRIPTION "latitude milliseconds value of GNSS position"
    ::= { hopfGnssPosLatitude 3 }

hopfGnssPosLatDir OBJECT-TYPE
    SYNTAX      INTEGER { north(0), south(1) }
    MAX-ACCESS  read-only
    STATUS      current
    DESCRIPTION "latitude direction from zero degree"
    ::= { hopfGnssPosLatitude 4 }

hopfError OBJECT IDENTIFIER ::= { hopfGnss 11 }

hopfErrorGNSSRawDataMode OBJECT-TYPE
    SYNTAX      INTEGER (0..1)
    MAX-ACCESS  read-only
    STATUS      current
    DESCRIPTION "GNSS receiver in raw data mode - no synchronization:
                 0 --> error off
                 1 --> error on"
    ::= { hopfError 1 }

hopfErrorGNSSCommErr OBJECT-TYPE
    SYNTAX      INTEGER (0..1)
    MAX-ACCESS  read-only
    STATUS      current
    DESCRIPTION "GNSS receiver communication error:
                 0 --> error off
                 1 --> error on"
    ::= { hopfError 2 }

hopfErrorRTC OBJECT-TYPE
    SYNTAX      INTEGER (0..1)
    MAX-ACCESS  read-only
    STATUS      current
    DESCRIPTION "RTC error:
                 0 --> error off
                 1 --> error on"
    ::= { hopfError 3 }

hopfErrorFRAM OBJECT-TYPE
    SYNTAX      INTEGER (0..1)
    MAX-ACCESS  read-only
    STATUS      current
    DESCRIPTION "FRAM error:
                 0 --> error off
                 1 --> error on"
    ::= { hopfError 4 }

hopfErrorAntennaCircuitOpen OBJECT-TYPE
    SYNTAX      INTEGER (0..1)
    MAX-ACCESS  read-only
    STATUS      current
    DESCRIPTION "Antenna circuit open error:
                 0 --> error off
                 1 --> error on"
    ::= { hopfError 5 }

hopfErrorAntennaCircuitShorted OBJECT-TYPE
    SYNTAX      INTEGER (0..1)
    MAX-ACCESS  read-only
    STATUS      current
    DESCRIPTION "Antenna circuit shorted error:
                 0 --> error off
                 1 --> error on"
    ::= { hopfError 6 }

hopfErrorCrystalRegulation OBJECT-TYPE
    SYNTAX      INTEGER (0..1)
    MAX-ACCESS  read-only
    STATUS      current
    DESCRIPTION "Adjustment of internal quartz frequency error:
                 0 --> error off
                 1 --> error on"
    ::= { hopfError 7 }

hopfErrorSPIO OBJECT-TYPE
    SYNTAX      INTEGER (0..1)
    MAX-ACCESS  read-only
    STATUS      current
    DESCRIPTION "SPIO setting error:
                 0 --> error off
                 1 --> error on"
    ::= { hopfError 8 }

hopfErrorDST OBJECT-TYPE
    SYNTAX      INTEGER (0..1)
    MAX-ACCESS  read-only
    STATUS      current
    DESCRIPTION "Missing or incomplete data for daylight saving time (DST):
                 0 --> error off
                 1 --> error on"
    ::= { hopfError 9 }

hopfErrorTimeZone OBJECT-TYPE
    SYNTAX      INTEGER (0..1)
    MAX-ACCESS  read-only
    STATUS      current
    DESCRIPTION "Missing data for Time Zone Offset:
                 0 --> error off
                 1 --> error on"
    ::= { hopfError 10 }

hopfErrorGNSSInit OBJECT-TYPE
    SYNTAX      INTEGER (0..1)
    MAX-ACCESS  read-only
    STATUS      current
    DESCRIPTION "GNSS receiver initialization active:
                 0 --> error off
                 1 --> error on"
    ::= { hopfError 11 }

hopfErrorPCID OBJECT-TYPE
    SYNTAX      INTEGER (0..1)
    MAX-ACCESS  read-only
    STATUS      current
    DESCRIPTION "General Module error (PCID):
                 0 --> error off
                 1 --> error on"
    ::= { hopfError 12 }


--
-- SNMP Trap Notifications
--
hopf6890traps OBJECT IDENTIFIER ::= { hopfFG6890G01 200 }

loginDataInvalid NOTIFICATION-TYPE
    STATUS  current
    DESCRIPTION
            "this notification is sent when the login credentials provided by a user are invalid"
    ::= { hopf6890traps 1 }

loginDuringCooldown NOTIFICATION-TYPE
    STATUS  current
    DESCRIPTION
            "this notification is sent when a user performs a login while being on login cooldown"
    ::= { hopf6890traps 2 }

passwordChanged NOTIFICATION-TYPE
    STATUS  current
    DESCRIPTION
            "this notification is sent when a user changes his (local) password"
    ::= { hopf6890traps 3 }

configUploaded NOTIFICATION-TYPE
    STATUS  current
    DESCRIPTION
            "this notification is sent when a new configuration is applied"
    ::= { hopf6890traps 4 }

firmwareUpdateCompleted NOTIFICATION-TYPE
    STATUS  current
    DESCRIPTION
            "this notification is sent when a firmware update has been completed"
    ::= { hopf6890traps 5 }

jwtKeyReset NOTIFICATION-TYPE
    STATUS  current
    DESCRIPTION
            "this notification is sent when a jwt secret reset has been triggered"
    ::= { hopf6890traps 6 }

certificateUploaded NOTIFICATION-TYPE
    STATUS  current
    DESCRIPTION
            "this notification is sent when a new certificate has been uploaded"
    ::= { hopf6890traps 7 }

antennaShorted NOTIFICATION-TYPE
    STATUS  current
    DESCRIPTION
            "this notification is sent when the antenna circuit has been shorted (e.g. cable damage)"
    ::= { hopf6890traps 8 }

antennaOpen NOTIFICATION-TYPE
    STATUS  current
    DESCRIPTION
            "this notification is sent when the antenna circuit has been opened (e.g. antenna disconnect or cable damage)"
    ::= { hopf6890traps 9 }

hardwareFailure NOTIFICATION-TYPE
    STATUS  current
    DESCRIPTION
            "this notification is sent when a hardware failure has been triggered (specific failure included in notification objects)"
    ::= { hopf6890traps 10 }
    
timeSet NOTIFICATION-TYPE
    OBJECTS { hopf6890SystemTime }
    STATUS  current
    DESCRIPTION
            "this notification is sent when the system time is set manually via action"
    ::= { hopf6890traps 11 }
	
leapAnnounceChanged NOTIFICATION-TYPE
    STATUS  current
    DESCRIPTION
            "this notification is sent when a leap second is announced (announcement occurs exactly one hour before leap second)"
    ::= { hopf6890traps 12 }
	
dstChanged NOTIFICATION-TYPE
    STATUS  current
    DESCRIPTION
            "this notification is sent when the system enters and leaves daylight saving time"
    ::= { hopf6890traps 13 }

dstIndicatorChanged NOTIFICATION-TYPE
    STATUS  current
    DESCRIPTION
            "this notification is sent when a daylight saving time change is announced (announcement occurs exactly one hour before dstChanged)"
    ::= { hopf6890traps 14 }

syncAccuracyChanged NOTIFICATION-TYPE
	OBJECTS { syncSourceTimeSyncAccuracy }
    STATUS  current
    DESCRIPTION
            "this notification is sent when the clock sync accuracy changes"
    ::= { hopf6890traps 15 }

syncStatusChanged NOTIFICATION-TYPE
	OBJECTS { syncSourceTimeSyncStatusInt }
    STATUS  current
    DESCRIPTION
            "this notification is sent when the clock sync status changes"
    ::= { hopf6890traps 16 }

systemRebootInitialized NOTIFICATION-TYPE
    STATUS  current
    DESCRIPTION
            "this notification is sent when a manual system reboot has been triggered"
    ::= { hopf6890traps 17 }
	
systemRebootCompleted NOTIFICATION-TYPE
    STATUS  current
    DESCRIPTION
            "this notification is sent when a system reboot has been completed"
    ::= { hopf6890traps 18 }
	
boardRebootInitialized NOTIFICATION-TYPE
    STATUS  current
    DESCRIPTION
            "this notification is sent when a manual board reboot has been triggered"
    ::= { hopf6890traps 19 }
	
boardRebootCompleted NOTIFICATION-TYPE
    STATUS  current
    DESCRIPTION
            "this notification is sent when a board reboot has been completed"
    ::= { hopf6890traps 20 }
	
systemFactoryResetInitialized NOTIFICATION-TYPE
    STATUS  current
    DESCRIPTION
            "this notification is sent when a system factory reset has been triggered"
    ::= { hopf6890traps 21 }
	
systemFactoryResetCompleted NOTIFICATION-TYPE
    STATUS  current
    DESCRIPTION
            "this notification is sent when a system factory reset has been completed"
    ::= { hopf6890traps 22 }
	
boardFactoryResetInitiated NOTIFICATION-TYPE
    STATUS  current
    DESCRIPTION
            "this notification is sent when a board factory reset has been triggered"
    ::= { hopf6890traps 23 }
	
boardFactoryResetCompleted NOTIFICATION-TYPE
    STATUS  current
    DESCRIPTION
            "this notification is sent when a board factory reset has been completed"
    ::= { hopf6890traps 24 }
	
keyInvalid NOTIFICATION-TYPE
    STATUS  current
    DESCRIPTION
            "this notification is sent when an invalid activation key is entered into the activation key field"
    ::= { hopf6890traps 25 }
	
keyActivated NOTIFICATION-TYPE
    STATUS  current
    DESCRIPTION
            "this notification is sent when a new activation key has been successfully added to the system"
    ::= { hopf6890traps 26 }
	
keyReset NOTIFICATION-TYPE
    STATUS  current
    DESCRIPTION
            "this notification is sent when all activation keys on the system have been manually reset"
    ::= { hopf6890traps 27 }

keysAssigned NOTIFICATION-TYPE
    STATUS  current
    DESCRIPTION
            "this notification is sent when a feature (activation key) has been assigned to a board"
    ::= { hopf6890traps 28 }

END
