-- File HOPF_FG8101GXX.MIB
-- Defines HOPF-FG8101GXX-MIB (hopf Eelektronik GmbH proprietary MIB for FG8101GXX)

-- HOPF-FG8101GXX-MIB { iso(1) org(3) dod(6) internet(1) private(4)
--               enterprises(1) hopf(12527) }

HOPF-FG8101GXX-MIB DEFINITIONS ::= BEGIN

--  (c) 2005-2025 by hopf Elektronik GmbH and RDCS Informationstechnologie GmbH

--  FILENAME        : HOPF_FG8101GXX.MIB
--  AUTHOR          : HOPF/POSCH
--  DATE OF CREATION: 2025-03-26

--  DESCRIPTION:
--  Definition of the proprietary MIB for FG8101GXX.
--  The NTP part of this MIB is partly implemented as proposed in the 
--  Technical Report No. 98-09 by Adarshpal S. Sethi and David Mills.

--  DOCUMENTATION OF CHANGES:

--  NUMBER  | AUTHOR |    DATE    | DESCRIPTION
--  --------+--------+------------+--------------------------------------------------------------
--  @00001  |  DAD   | 2025-01-07 | Adapted the FG8101G01-MIB to FG8101GXX-MIB
--  --------+--------+------------+--------------------------------------------------------------
--  @00002	|  DAD	 | 2025-03-26 | Added firewallAlarm to trap list (50)
--  --------+--------+------------+--------------------------------------------------------------
--  @00003	|  MAC	 | 2025-06-23 | Added systemStatusChanged (51) and boardStatusChanged (52) to trap list
--			|  DAD   | 2025-11-07 | Added gnssVelocityNorth, gnssVelocityEast, gnssVelocityDown, gnssGroundSpeed, gnssHeadingOfMotion, gnssEllipsoidHeight, gnssSealevelHeight
--			|		 |			  | Added gnss2VelocityNorth, gnss2VelocityEast, gnss2VelocityDown, gnss2GroundSpeed, gnss2HeadingOfMotion, gnss2EllipsoidHeight, gnss2SealevelHeight
--  --------+--------+------------+--------------------------------------------------------------


IMPORTS
    MODULE-IDENTITY, OBJECT-TYPE,
    enterprises, Integer32, NOTIFICATION-TYPE
        FROM SNMPv2-SMI
    TEXTUAL-CONVENTION, DisplayString
        FROM SNMPv2-TC;

--
-- The position of the FG8101GXX within the enterprise
--
hopfFG8101GXX MODULE-IDENTITY
     LAST-UPDATED "202501070000Z"
     ORGANIZATION "hopf Elektronik GmbH"
     CONTACT-INFO
        "Markus Posch
         hopf Elektronik GmbH
         Nottebohmstrasse 41
         58511 Luedenscheid
         Germany
         Tel: +49-2351-938686
         eMail: support@hopf.com

         Wolfgang KANOVSKY
         RDCS Informationstechnologie GmbH
         Embelgasse 66/10-11
         1050 Vienna
         Austria
         Tel: +43-1-5455077-0
         eMail: support@rdcs.eu"
     DESCRIPTION
        "This MIB module defines a MIB which provides mechanisms to
         monitor and control the FG8101GXX."
     REVISION "202501070000Z"
     DESCRIPTION
        "Syntax error corrections."
     ::= { hopf 100 }

--
-- The position of the enterprise within the OID hierarchy of this MIB:
--
hopf OBJECT IDENTIFIER ::= { enterprises 12527 }

--
-- Definitions for the general device informations:
--
general OBJECT IDENTIFIER ::= { hopfFG8101GXX 1 }

productNumber OBJECT-TYPE
    SYNTAX      DisplayString (SIZE (0..32))
    MAX-ACCESS  read-only
    STATUS      current
    DESCRIPTION "Product number of the device"
    ::= { general 1 }

serialNumber OBJECT-TYPE
    SYNTAX      DisplayString (SIZE (0..32))
    MAX-ACCESS  read-only
    STATUS      current
    DESCRIPTION "Serial number of the device, unique for this product type"
    ::= { general 2 }

firmwareVersion OBJECT-TYPE
    SYNTAX      DisplayString (SIZE (0..5))
    MAX-ACCESS  read-only
    STATUS      current
    DESCRIPTION "String which describes the current version of
                 the device software for the embedded sub-system.
                 version numbers are two digits for the major version and
                 two digits for the minor version divided by a dot (e.g. 01.00)"
    ::= { general 3 }

status OBJECT-TYPE
    SYNTAX      INTEGER { ok(0), warning(1), error(2) }
    MAX-ACCESS  read-only
    STATUS      current
    DESCRIPTION "Current system status"
    ::= { general 4 }

uptime OBJECT-TYPE
    SYNTAX      OCTET STRING
    MAX-ACCESS  read-only
    STATUS      current
    DESCRIPTION "Current Uptime of the device."
    ::= { general 5 }

hostname OBJECT-TYPE
    SYNTAX      OCTET STRING
    MAX-ACCESS  read-only
    STATUS      current
    DESCRIPTION "Hostname of the management board"
    ::= { general 6 }

location OBJECT-TYPE
    SYNTAX      OCTET STRING
    MAX-ACCESS  read-only
    STATUS      current
    DESCRIPTION "Configured location name"
    ::= { general 7 }

--
-- Definitions for the detailed device status:
--
systemDetails OBJECT IDENTIFIER ::= { hopfFG8101GXX 2 }

temperatureLeft OBJECT-TYPE
    SYNTAX      DisplayString (SIZE (0..32))
    MAX-ACCESS  read-only
    STATUS      current
    DESCRIPTION "Measured  temperature in degree Celsius at the left side of the system"
    ::= { systemDetails 1 }

temperatureRight OBJECT-TYPE
    SYNTAX      DisplayString (SIZE (0..32))
    MAX-ACCESS  read-only
    STATUS      current
    DESCRIPTION "Measured  temperature in degree Celsius at the left side of the system"
    ::= { systemDetails 2 }

fanStatusLeft OBJECT-TYPE
    SYNTAX      INTEGER { ok(0), warning(1), error(2) }
    MAX-ACCESS  read-only
    STATUS      current
    DESCRIPTION "Status of the left fan"
    ::= { systemDetails 3 }

fanStatusRight OBJECT-TYPE
    SYNTAX      INTEGER { ok(0), warning(1), error(2) }
    MAX-ACCESS  read-only
    STATUS      current
    DESCRIPTION "Status of the right fan"
    ::= { systemDetails 4 }

fanSpeedLeft OBJECT-TYPE
    SYNTAX      INTEGER (0..100)
    MAX-ACCESS  read-only
    STATUS      current
    DESCRIPTION "Speed of the left fan in percent"
    ::= { systemDetails 5 }

fanSpeedRight OBJECT-TYPE
    SYNTAX      INTEGER (0..100)
    MAX-ACCESS  read-only
    STATUS      current
    DESCRIPTION "Speed of the right fan in percent"
    ::= { systemDetails 6 }


--
-- Definitions for the boards of the system:
--
boards OBJECT IDENTIFIER ::= { hopfFG8101GXX 3 }

boardsVarTable OBJECT-TYPE
    SYNTAX      SEQUENCE OF BoardsVarEntry
    MAX-ACCESS  not-accessible
    STATUS      current
    DESCRIPTION ""
    ::= { boards 1 }

boardsVarEntry OBJECT-TYPE
    SYNTAX      BoardsVarEntry
    MAX-ACCESS  not-accessible
    STATUS      current
    DESCRIPTION ""
    INDEX       { boardPosition }
    ::= { boardsVarTable 1 }

BoardsVarEntry ::= SEQUENCE {
    boardPosition           OCTET STRING,
    boardProductName        OCTET STRING,
    boardSerialNumber       OCTET STRING,
    boardFirmwareVersion    DisplayString,
    boardStatus             INTEGER,
    boardUptime             OCTET STRING,
    psuDetails              OBJECT IDENTIFIER,
    network                 OBJECT IDENTIFIER,
    syncSource              OBJECT IDENTIFIER,
    syncSourceGnss          OBJECT IDENTIFIER,
    timeService             OBJECT IDENTIFIER
    }

boardPosition OBJECT-TYPE
    SYNTAX      OCTET STRING (SIZE(0..64))
    MAX-ACCESS  read-only
    STATUS      current
    DESCRIPTION "Position of the board inside the system"
    ::= { boardsVarEntry 1 }

boardProductName OBJECT-TYPE
    SYNTAX      OCTET STRING (SIZE(0..64))
    MAX-ACCESS  read-only
    STATUS      current
    DESCRIPTION "Product name of the board"
    ::= { boardsVarEntry 2 }

boardSerialNumber OBJECT-TYPE
    SYNTAX      OCTET STRING (SIZE(0..64))
    MAX-ACCESS  read-only
    STATUS      current
    DESCRIPTION "Serial number of the board"
    ::= { boardsVarEntry 3 }

boardFirmwareVersion OBJECT-TYPE
    SYNTAX      DisplayString (SIZE (0..5))
    MAX-ACCESS  read-only
    STATUS      current
    DESCRIPTION "String which describes the current version of
                 the device software for the embedded sub-system.
                 version numbers are two digits for the major version and
                 two digits for the minor version divided by a dot (e.g. 01.00)"
    ::= { boardsVarEntry 4 }

boardStatus OBJECT-TYPE
    SYNTAX      INTEGER { ok(0), warning(1), error(2) }
    MAX-ACCESS  read-only
    STATUS      current
    DESCRIPTION "Current system status"
    ::= { boardsVarEntry 5 }

boardUptime OBJECT-TYPE
    SYNTAX      OCTET STRING
    MAX-ACCESS  read-only
    STATUS      current
    DESCRIPTION "Current Uptime of the device."
    ::= { boardsVarEntry 6 }

--
-- Status informations only valid for power supply boards:
--
psuDetails OBJECT IDENTIFIER ::= { boardsVarEntry 7 }

psuOutputVoltage OBJECT-TYPE
    SYNTAX      OCTET STRING (SIZE(0..64))
    MAX-ACCESS  read-only
    STATUS      current
    DESCRIPTION "Output voltage of the power supply unit"
    ::= { psuDetails 1 }

psuOutputCurrent OBJECT-TYPE
    SYNTAX      OCTET STRING (SIZE(0..64))
    MAX-ACCESS  read-only
    STATUS      current
    DESCRIPTION "Output current of the power supply unit"
    ::= { psuDetails 2 }

psuOutputPower OBJECT-TYPE
    SYNTAX      OCTET STRING (SIZE(0..64))
    MAX-ACCESS  read-only
    STATUS      current
    DESCRIPTION "Output power of the power supply unit"
    ::= { psuDetails 3 }

psuTemperature OBJECT-TYPE
    SYNTAX      OCTET STRING (SIZE(0..64))
    MAX-ACCESS  read-only
    STATUS      current
    DESCRIPTION "Temperature of the power supply unit"
    ::= { psuDetails 4 }

--
-- Network status informations only valid for boards with network interfaces:
--
network OBJECT IDENTIFIER ::= { boardsVarEntry 8 }

networkEth0LinkUp OBJECT-TYPE
    SYNTAX      INTEGER { down(0), up(1) }
    MAX-ACCESS  read-only
    STATUS      current
    DESCRIPTION "Link status of network interface 0"
    ::= { network 1 }

networkEth0Mac OBJECT-TYPE
    SYNTAX      OCTET STRING
    MAX-ACCESS  read-only
    STATUS      current
    DESCRIPTION "Mac address of network interface 0"
    ::= { network 2 }

networkEth0Ip OBJECT-TYPE
    SYNTAX      OCTET STRING
    MAX-ACCESS  read-only
    STATUS      current
    DESCRIPTION "IP address of network interface 0"
    ::= { network 3 }

networkEth1LinkUp OBJECT-TYPE
    SYNTAX      INTEGER { down(0), up(1) }
    MAX-ACCESS  read-only
    STATUS      current
    DESCRIPTION "Link status of network interface 1"
    ::= { network 4 }

networkEth1Mac OBJECT-TYPE
    SYNTAX      OCTET STRING
    MAX-ACCESS  read-only
    STATUS      current
    DESCRIPTION "Mac address of network interface 1"
    ::= { network 5 }

networkEth1Ip OBJECT-TYPE
    SYNTAX      OCTET STRING
    MAX-ACCESS  read-only
    STATUS      current
    DESCRIPTION "IP address of network interface 1"
    ::= { network 6 }

--
-- Synchronization status of the board:
--
syncSource OBJECT IDENTIFIER ::= { boardsVarEntry 9 }

syncSourceSimulationMode OBJECT-TYPE
    SYNTAX      INTEGER { off(0), on(1) }
    MAX-ACCESS  read-only
    STATUS      current
    DESCRIPTION "Displays if the simulation mode is active"
    ::= { syncSource 1 }

syncSourceSyncState OBJECT-TYPE
    SYNTAX      INTEGER { invalid(0), crystal(1), synchronous(2) }
    MAX-ACCESS  read-only
    STATUS      current
    DESCRIPTION "Synchronization state of the board"
    ::= { syncSource 2 }

syncSourceSyncAccuracy OBJECT-TYPE
    SYNTAX      INTEGER
    MAX-ACCESS  read-only
    STATUS      current
    DESCRIPTION "Synchronization accuracy of the board in nanoseconds"
    ::= { syncSource 3 }

syncSourceSyncSource OBJECT-TYPE
    SYNTAX      INTEGER { no(0), timedomain1(1), timedomain2(2), gnss(3), ptp(4), ntp(5), holdover(6) }
    MAX-ACCESS  read-only
    STATUS      current
    DESCRIPTION "Synchronization source of the board"
    ::= { syncSource 4 }

syncSourceLeapIndication OBJECT-TYPE
    SYNTAX      INTEGER { no(0), positive(1), negative(2) }
    MAX-ACCESS  read-only
    STATUS      current
    DESCRIPTION "Leap second announce status"
    ::= { syncSource 5 }

--
-- Synchronization status of the board:
--
syncSourceGnss OBJECT IDENTIFIER ::= { boardsVarEntry 10 }

gnssSatTracked OBJECT-TYPE
    SYNTAX      INTEGER
    MAX-ACCESS  read-only
    STATUS      current
    DESCRIPTION "Number of tracked GNSS satellites"
    ::= { syncSourceGnss 1 }

gnssJammingState OBJECT-TYPE
    SYNTAX      INTEGER { notConfigured(0), initializing(1), noJamming(2), jammingDetected(3) }
    MAX-ACCESS  read-only
    STATUS      current
    DESCRIPTION "Jamming state"
    ::= { syncSourceGnss 2 }

gnssSpoofingState OBJECT-TYPE
    SYNTAX      INTEGER { notConfigured(0), initializing(1), noSpoofing(2), spoofingDetected(3) }
    MAX-ACCESS  read-only
    STATUS      current
    DESCRIPTION "Spoofing state"
    ::= { syncSourceGnss 3 }
	
gnssAntennaOpenDetected OBJECT-TYPE
    SYNTAX      INTEGER { notOpen(0), open(1) }
    MAX-ACCESS  read-only
    STATUS      current
    DESCRIPTION "Antenna open"
    ::= { syncSourceGnss 4 }
	
gnssAntennaShortCircuitDetected OBJECT-TYPE
    SYNTAX      INTEGER { noShortCircuit(0), shortCircuit(1) }
    MAX-ACCESS  read-only
    STATUS      current
    DESCRIPTION "Antenna short circuit"
    ::= { syncSourceGnss 5 }

gnss2SatTracked OBJECT-TYPE
    SYNTAX      INTEGER
    MAX-ACCESS  read-only
    STATUS      current
    DESCRIPTION "Number of tracked GNSS satellites"
    ::= { syncSourceGnss 6 }

gnss2JammingState OBJECT-TYPE
    SYNTAX      INTEGER { notConfigured(0), initializing(1), noJamming(2), jammingDetected(3) }
    MAX-ACCESS  read-only
    STATUS      current
    DESCRIPTION "Jamming state"
    ::= { syncSourceGnss 7 }

gnss2SpoofingState OBJECT-TYPE
    SYNTAX      INTEGER { notConfigured(0), initializing(1), noSpoofing(2), spoofingDetected(3) }
    MAX-ACCESS  read-only
    STATUS      current
    DESCRIPTION "Spoofing state"
    ::= { syncSourceGnss 8 }
	
gnss2AntennaOpenDetected OBJECT-TYPE
    SYNTAX      INTEGER { notOpen(0), open(1) }
    MAX-ACCESS  read-only
    STATUS      current
    DESCRIPTION "Antenna open"
    ::= { syncSourceGnss 9 }
	
gnss2AntennaShortCircuitDetected OBJECT-TYPE
    SYNTAX      INTEGER { noShortCircuit(0), shortCircuit(1) }
    MAX-ACCESS  read-only
    STATUS      current
    DESCRIPTION "Antenna short circuit"
    ::= { syncSourceGnss 10 }

gnssEllipsoidHeight OBJECT-TYPE
    SYNTAX      INTEGER
    MAX-ACCESS  read-only
    STATUS      current
    DESCRIPTION "Elliposid height of the antenna"
    ::= { syncSourceGnss 11 }

gnssSealevelHeight OBJECT-TYPE
    SYNTAX      INTEGER
    MAX-ACCESS  read-only
    STATUS      current
    DESCRIPTION "Sealevel height of the antenna"
    ::= { syncSourceGnss 12 }

gnssVelocityNorth OBJECT-TYPE
    SYNTAX      DisplayString (SIZE (0..32))
    MAX-ACCESS  read-only
    STATUS      current
    DESCRIPTION "North velocity"
    ::= { syncSourceGnss 13 }

gnssVelocityEast OBJECT-TYPE
    SYNTAX      DisplayString (SIZE (0..32))
    MAX-ACCESS  read-only
    STATUS      current
    DESCRIPTION "East velocity"
    ::= { syncSourceGnss 14 }

gnssVelocityDown OBJECT-TYPE
    SYNTAX      DisplayString (SIZE (0..32))
    MAX-ACCESS  read-only
    STATUS      current
    DESCRIPTION "Down velocity"
    ::= { syncSourceGnss 15 }

gnssGroundSpeed OBJECT-TYPE
    SYNTAX      INTEGER
    MAX-ACCESS  read-only
    STATUS      current
    DESCRIPTION "Ground Speed"
    ::= { syncSourceGnss 16 }

gnssHeadingOfMotion OBJECT-TYPE
    SYNTAX      INTEGER
    MAX-ACCESS  read-only
    STATUS      current
    DESCRIPTION "Heading of motion"
    ::= { syncSourceGnss 17 }

gnss2EllipsoidHeight OBJECT-TYPE
    SYNTAX      INTEGER
    MAX-ACCESS  read-only
    STATUS      current
    DESCRIPTION "Elliposid height of the antenna"
    ::= { syncSourceGnss 18 }

gnss2SealevelHeight OBJECT-TYPE
    SYNTAX      INTEGER
    MAX-ACCESS  read-only
    STATUS      current
    DESCRIPTION "Sealevel height of the antenna"
    ::= { syncSourceGnss 19 }

gnss2VelocityNorth OBJECT-TYPE
    SYNTAX      INTEGER
    MAX-ACCESS  read-only
    STATUS      current
    DESCRIPTION "North velocity"
    ::= { syncSourceGnss 20 }

gnss2VelocityEast OBJECT-TYPE
    SYNTAX      INTEGER
    MAX-ACCESS  read-only
    STATUS      current
    DESCRIPTION "East velocity"
    ::= { syncSourceGnss 21 }

gnss2VelocityDown OBJECT-TYPE
    SYNTAX      INTEGER
    MAX-ACCESS  read-only
    STATUS      current
    DESCRIPTION "Down velocity"
    ::= { syncSourceGnss 22 }

gnss2GroundSpeed OBJECT-TYPE
    SYNTAX      INTEGER
    MAX-ACCESS  read-only
    STATUS      current
    DESCRIPTION "Ground speed"
    ::= { syncSourceGnss 23 }

gnss2HeadingOfMotion OBJECT-TYPE
    SYNTAX      INTEGER
    MAX-ACCESS  read-only
    STATUS      current
    DESCRIPTION "Heading of motion"
    ::= { syncSourceGnss 24 }


--
-- Status of the time services of the board:
--
timeService OBJECT IDENTIFIER ::= { boardsVarEntry 11 }

timeServiceAccuracy OBJECT-TYPE
    SYNTAX      INTEGER
    MAX-ACCESS  read-only
    STATUS      current
    DESCRIPTION "Accuracy of all timeservice provided by this board in nanoseconds"
    ::= { timeService 1 }

timeServiceNtpRunning OBJECT-TYPE
    SYNTAX      INTEGER { notRunning(0), running(1) }
    MAX-ACCESS  read-only
    STATUS      current
    DESCRIPTION "Running state of the NTP service"
    ::= { timeService 2 }

timeServicePtpRunning OBJECT-TYPE
    SYNTAX      INTEGER { notRunning(0), running(1) }
    MAX-ACCESS  read-only
    STATUS      current
    DESCRIPTION "Running state of the PTP service"
    ::= { timeService 3 }

timeServiceSimaticRunning OBJECT-TYPE
    SYNTAX      INTEGER { notRunning(0), running(1) }
    MAX-ACCESS  read-only
    STATUS      current
    DESCRIPTION "Running state of the SIMATIC service"
    ::= { timeService 4 }

timeServiceX1Running OBJECT-TYPE
    SYNTAX      INTEGER { notRunning(0), running(1) }
    MAX-ACCESS  read-only
    STATUS      current
    DESCRIPTION "Running state of the service on connector X1"
    ::= { timeService 5 }

timeServiceX2Running OBJECT-TYPE
    SYNTAX      INTEGER { notRunning(0), running(1) }
    MAX-ACCESS  read-only
    STATUS      current
    DESCRIPTION "Running state of the service on connector X2"
    ::= { timeService 6 }

timeServiceX3Running OBJECT-TYPE
    SYNTAX      INTEGER { notRunning(0), running(1) }
    MAX-ACCESS  read-only
    STATUS      current
    DESCRIPTION "Running state of the service on connector X3"
    ::= { timeService 7 }

timeServiceX4Running OBJECT-TYPE
    SYNTAX      INTEGER { notRunning(0), running(1) }
    MAX-ACCESS  read-only
    STATUS      current
    DESCRIPTION "Running state of the service on connector X4"
    ::= { timeService 8 }

timeServiceSinech1Running OBJECT-TYPE
    SYNTAX      INTEGER { notRunning(0), running(1) }
    MAX-ACCESS  read-only
    STATUS      current
    DESCRIPTION "Running state of the SINEC H1 service"
    ::= { timeService 9 }
	
timeServiceNtpStratum OBJECT-TYPE
    SYNTAX      INTEGER
    MAX-ACCESS  read-only
    STATUS      current
    DESCRIPTION "Stratum of NTP service"
    ::= { timeService 10 }

--
-- SNMP Trap Notifications
--
hopfTraps OBJECT IDENTIFIER ::= { hopfFG8101GXX 200 }

loginDataInvalid NOTIFICATION-TYPE
    STATUS  current
    DESCRIPTION
            "this notification is sent when the login credentials provided by a user are invalid"
    ::= { hopfTraps 1 }

loginDuringCooldown NOTIFICATION-TYPE
    STATUS  current
    DESCRIPTION
            "this notification is sent when a user performs a login while being on login cooldown"
    ::= { hopfTraps 2 }

passwordChanged NOTIFICATION-TYPE
    STATUS  current
    DESCRIPTION
            "this notification is sent when a user changes his (local) password"
    ::= { hopfTraps 3 }

configUploaded NOTIFICATION-TYPE
    STATUS  current
    DESCRIPTION
            "this notification is sent when a new configuration is applied"
    ::= { hopfTraps 4 }

firmwareUpdateCompleted NOTIFICATION-TYPE
    STATUS  current
    DESCRIPTION
            "this notification is sent when a firmware update has been completed"
    ::= { hopfTraps 5 }

jwtKeyReset NOTIFICATION-TYPE
    STATUS  current
    DESCRIPTION
            "this notification is sent when a jwt secret reset has been triggered"
    ::= { hopfTraps 6 }

certificateUploaded NOTIFICATION-TYPE
    STATUS  current
    DESCRIPTION
            "this notification is sent when a new certificate has been uploaded"
    ::= { hopfTraps 7 }

antennaShorted NOTIFICATION-TYPE
    STATUS  current
    DESCRIPTION
            "this notification is sent when the antenna circuit has been shorted (e.g. cable damage)"
    ::= { hopfTraps 8 }

antennaOpen NOTIFICATION-TYPE
    STATUS  current
    DESCRIPTION
            "this notification is sent when the antenna circuit has been opened (e.g. antenna disconnect or cable damage)"
    ::= { hopfTraps 9 }
    
timeSet NOTIFICATION-TYPE
    STATUS  current
    DESCRIPTION
            "this notification is sent when the system time is set manually via action"
    ::= { hopfTraps 11 }
	
leapAnnounceChanged NOTIFICATION-TYPE
    STATUS  current
    DESCRIPTION
            "this notification is sent when a leap second is announced (announcement occurs exactly one hour before leap second)"
    ::= { hopfTraps 12 }

syncAccuracyChanged NOTIFICATION-TYPE
    STATUS  current
    DESCRIPTION
            "this notification is sent when the clock sync accuracy changes"
    ::= { hopfTraps 15 }

syncStatusChanged NOTIFICATION-TYPE
    STATUS  current
    DESCRIPTION
            "this notification is sent when the clock sync status changes"
    ::= { hopfTraps 16 }

systemRebootInitiated NOTIFICATION-TYPE
    STATUS  current
    DESCRIPTION
            "this notification is sent when a manual system reboot has been triggered"
    ::= { hopfTraps 17 }
	
boardRebootInitiated NOTIFICATION-TYPE
    STATUS  current
    DESCRIPTION
            "this notification is sent when a manual board reboot has been triggered"
    ::= { hopfTraps 19 }
	
boardRebootCompleted NOTIFICATION-TYPE
    STATUS  current
    DESCRIPTION
            "this notification is sent when a board reboot has been completed"
    ::= { hopfTraps 20 }
	
systemFactoryResetInitiated NOTIFICATION-TYPE
    STATUS  current
    DESCRIPTION
            "this notification is sent when a system factory reset has been triggered"
    ::= { hopfTraps 21 }
	
boardFactoryResetInitiated NOTIFICATION-TYPE
    STATUS  current
    DESCRIPTION
            "this notification is sent when a board factory reset has been triggered"
    ::= { hopfTraps 23 }
	
keyInvalid NOTIFICATION-TYPE
    STATUS  current
    DESCRIPTION
            "this notification is sent when an invalid activation key is entered into the activation key field"
    ::= { hopfTraps 25 }
	
keyActivated NOTIFICATION-TYPE
    STATUS  current
    DESCRIPTION
            "this notification is sent when a new activation key has been successfully added to the system"
    ::= { hopfTraps 26 }
	
keyReset NOTIFICATION-TYPE
    STATUS  current
    DESCRIPTION
            "this notification is sent when all activation keys on the system have been manually reset"
    ::= { hopfTraps 27 }
	
unauthTokenRefresh NOTIFICATION-TYPE
    STATUS  current
    DESCRIPTION
            "this notification is sent when an unauthenticated token refresh happens"
    ::= { hopfTraps 29 }
	
configSignatureFailure NOTIFICATION-TYPE
    STATUS  current
    DESCRIPTION
            "this notification is sent when an config with a wrong signature is uploaded to the device"
    ::= { hopfTraps 30 }
	
firmwareSignatureFailure NOTIFICATION-TYPE
    STATUS  current
    DESCRIPTION
            "this notification is sent when an firmware with a wrong signature is uploaded to the device"
    ::= { hopfTraps 31 }
	
jammingDetected NOTIFICATION-TYPE
    STATUS  current
    DESCRIPTION
            "this notification is sent when jamming has been detected"
    ::= { hopfTraps 32 }
	
spoofingDetected NOTIFICATION-TYPE
    STATUS  current
    DESCRIPTION
            "this notification is sent when spoofig has been detected"
    ::= { hopfTraps 33 }
	
jammingNoLongerDetected NOTIFICATION-TYPE
    STATUS  current
    DESCRIPTION
            "this notification is sent when jamming is no longer detected"
    ::= { hopfTraps 34 }
	
spoofingNoLongerDetected NOTIFICATION-TYPE
    STATUS  current
    DESCRIPTION
            "this notification is sent when spoofing is no longer detected"
    ::= { hopfTraps 35 }
	
hardwareFailureDetected NOTIFICATION-TYPE
    STATUS  current
    DESCRIPTION
            "this notification is sent when a hardware failure has been detected"
    ::= { hopfTraps 36 }
	
hardwareFailureNoLongerDetected NOTIFICATION-TYPE
    STATUS  current
    DESCRIPTION
            "this notification is sent when a hardware failure is no longer detected"
    ::= { hopfTraps 37 }
	
antennaOpenNoLongerDetected NOTIFICATION-TYPE
    STATUS  current
    DESCRIPTION
            "this notification is sent when antenna circuit open is no longer detected"
    ::= { hopfTraps 38 }
	
timeServiceStarted NOTIFICATION-TYPE
    STATUS  current
    DESCRIPTION
            "this notification is sent when a time service has been started"
    ::= { hopfTraps 39 }
	
timeServiceStopped NOTIFICATION-TYPE
    STATUS  current
    DESCRIPTION
            "this notification is sent when a time service has been stoped"
    ::= { hopfTraps 40 }
	
softwareModuleFailure NOTIFICATION-TYPE
    STATUS  current
    DESCRIPTION
            "this notification is sent when a software module failure has been detected"
    ::= { hopfTraps 41 }
	
softwareFailureDetected NOTIFICATION-TYPE
    STATUS  current
    DESCRIPTION
            "this notification is sent when a software failure has been detected"
    ::= { hopfTraps 42 }
	
softwareFailureNoLongerDetected NOTIFICATION-TYPE
    STATUS  current
    DESCRIPTION
            "this notification is sent when a software failure is no longer detected"
    ::= { hopfTraps 43 }
	
antennaShortedNoLongerDetected NOTIFICATION-TYPE
    STATUS  current
    DESCRIPTION
            "this notification is sent when antenna circuit shorted is no longer detected"
    ::= { hopfTraps 44 }

antennaShortedGnss2 NOTIFICATION-TYPE
    STATUS  current
    DESCRIPTION
            "this notification is sent when the antenna circuit of GNSS2 has been shorted (e.g. cable damage)"
    ::= { hopfTraps 45 }

antennaShortedNoLongerDetectedGnss2 NOTIFICATION-TYPE
    STATUS  current
    DESCRIPTION
            "this notification is sent when antenna circuit shorted of GNSS2 is no longer detected"
    ::= { hopfTraps 46 }

antennaOpenGnss2 NOTIFICATION-TYPE
    STATUS  current
    DESCRIPTION
            "this notification is sent when the antenna circuit of GNSS2 has been opened (e.g. antenna disconnect or cable damage)"
    ::= { hopfTraps 47 }

antennaOpenNoLongerDetectedGnss2 NOTIFICATION-TYPE
    STATUS  current
    DESCRIPTION
            "this notification is sent when antenna circuit open of GNSS2 is no longer detected"
    ::= { hopfTraps 48 }

loginDataValid NOTIFICATION-TYPE
    STATUS  current
    DESCRIPTION
            "this notification is sent when the login credentials provided by a user are valid"
    ::= { hopfTraps 49 }
	
firewallAlarm NOTIFICATION-TYPE
    STATUS  current
    DESCRIPTION
            "this notification is sent when the configured firewall alarm options were exceeded"
    ::= { hopfTraps 50 }

systemStatusChanged NOTIFICATION-TYPE
    STATUS  current
    DESCRIPTION
            "this notification is sent when the system status changes"
    ::= { hopfTraps 51 }

boardStatusChanged NOTIFICATION-TYPE
    STATUS  current
    DESCRIPTION
            "this notification is sent when the board status changes"
    ::= { hopfTraps 52 }

hopfTrapGeneratorPosition OBJECT-TYPE
    SYNTAX      OCTET STRING (SIZE(0..256))
    MAX-ACCESS  read-only
    STATUS      current
    DESCRIPTION "identifies the board position inside the system, that generated the trap."
    ::= { hopfTraps 1000 }

hopfTrapAdditionalInformation OBJECT-TYPE
    SYNTAX      OCTET STRING (SIZE(0..256))
    MAX-ACCESS  read-only
    STATUS      current
    DESCRIPTION "adds aditional information to the trap."
    ::= { hopfTraps 1001 }

END
