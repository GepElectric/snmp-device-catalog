SicamRTUs  DEFINITIONS ::= BEGIN
	IMPORTS
        MODULE-IDENTITY, OBJECT-TYPE, NOTIFICATION-TYPE, Integer32 
		    FROM SNMPv2-SMI
		DisplayString                           
			FROM SNMPv2-TC
	    sicamRTUs
			FROM SIEMENS-SMI;

	generalInfo  MODULE-IDENTITY
		LAST-UPDATED	"201909031613Z"
		ORGANIZATION	"Siemens"
		CONTACT-INFO	"support.ic@siemens.com"
		DESCRIPTION		"The SICAM RTUs MIB module for managing settings
                        of the SIEMENS SICAM RTUs."
						
		REVISION		"201909031613Z"
		DESCRIPTION		"Included device in auConfigurationOverview"	
						
		REVISION		"201702141613Z"
		DESCRIPTION		"Included new error classes of sumDiagnosticTable 
		                 and table of FW versions "						
	    
		REVISION		"201602051613Z"
		DESCRIPTION		"Included history for traps"
		
		REVISION		"201506181613Z"	
	    DESCRIPTION     "Included SICAM RTUs diagnosis traps"	
		
		REVISION		"201403050913Z"	
	    DESCRIPTION     "Initial Version"	
		
		::=  {  sicamRTUs  1  }

    auConfigurationOverview     OBJECT IDENTIFIER ::= { generalInfo 1 }
    firmwareRevision            OBJECT IDENTIFIER ::= { generalInfo 2 }
    diagnostic                  OBJECT IDENTIFIER ::= { sicamRTUs 10 }
	history                     OBJECT IDENTIFIER ::= { sicamRTUs 11 }
    sumDiagnosticTable          OBJECT IDENTIFIER ::= { diagnostic 1 }
    sumDiagnosticTraps          OBJECT IDENTIFIER ::= { diagnostic 10 }

	
	DateAndTime ::= OCTET STRING (SIZE (8 | 11))
   --        A date-time specification for the local time of day.
   --        This data type is intended to provide a consistent
   --        method of reporting date information.
   --
   --            field  octets  contents                  range
   --            _____  ______  ________                  _____
   --              1      1-2   year                      0..65536
   --                           (in network byte order)
   --              2       3    month                     1..12
   --              3       4    day                       1..31
   --              4       5    hour                      0..23
   --              5       6    minutes                   0..59
   --              6       7    seconds                   0..60
   --                           (use 60 for leap-second)
   --              7       8    deci-seconds              0..9
   --              8       9    direction from UTC        "+" / "-"
   --                           (in ascii notation)
   --              9      10    hours from UTC            0..11
   --             10      11    minutes from UTC          0..59
   --
   --            Note that if only local time is known, then
   --            timezone information (fields 8-10) is not present.
	
	
	plant	OBJECT-TYPE	
		SYNTAX  DisplayString 
		MAX-ACCESS		read-only
		STATUS			current
		DESCRIPTION		"Plant name of the automation unit"
        -- 1.3.6.1.4.1.22638.7.1.1.1
		::=  { auConfigurationOverview  1 }

    plantID OBJECT-TYPE	
    	SYNTAX  DisplayString 
		MAX-ACCESS		read-only
		STATUS			current
		DESCRIPTION		"Plant id of the automation unit"
        -- 1.3.6.1.4.1.22638.7.1.1.2
		::=  { auConfigurationOverview  2 }


	region  OBJECT-TYPE	
		SYNTAX  INTEGER (0..249)
		MAX-ACCESS		read-only
		STATUS			current
		DESCRIPTION		"Region number of the automation unit (0 .. 249)"
		::=  { auConfigurationOverview  3 }

	component  OBJECT-TYPE	
		SYNTAX  INTEGER (0..255)
		MAX-ACCESS		read-only
		STATUS			current
		DESCRIPTION		"Component number of the automation unit (0 .. 255)"
		::=  { auConfigurationOverview  4 }
	
	device	OBJECT-TYPE	
		SYNTAX  DisplayString 
		MAX-ACCESS		read-only
		STATUS			current
		DESCRIPTION		"Device name of the automation unit"
        -- 1.3.6.1.4.1.22638.7.1.1.5
		::=  { auConfigurationOverview  5 }
		
	firmwareRevisionTable          OBJECT-TYPE
		SYNTAX      SEQUENCE OF FirmwareRevisionEntry
		MAX-ACCESS  not-accessible
		STATUS      current
		DESCRIPTION
			" "
		::= { firmwareRevision 1 }

	firmwareRevisionEntry  OBJECT-TYPE
		SYNTAX      FirmwareRevisionEntry
		MAX-ACCESS  not-accessible
		STATUS      current
		DESCRIPTION
			 "An entry in the list of last send SICAM RTUs firmware revision"
		INDEX       { rIndex }
		::= { firmwareRevisionTable 1 }

	FirmwareRevisionEntry ::=
		SEQUENCE {
			rIndex              Integer32,
			rInstance           DisplayString,			
			rName               DisplayString,
			rRevision           DisplayString,
			rDescription        DisplayString,
			rBseSse             DisplayString,
			rHwNr               DisplayString,			
			rFwNr               DisplayString			
	}		
		
	rIndex OBJECT-TYPE
		SYNTAX      Integer32 (0..16383)
		MAX-ACCESS  read-only
		STATUS      current
		DESCRIPTION "Index of last send SICAM RTUs firmware information"
		::= { firmwareRevisionEntry 1 }
	
	 rInstance OBJECT-TYPE
		SYNTAX      DisplayString
		MAX-ACCESS  read-only
		STATUS current
		DESCRIPTION "Instance of the system element"
		::= { firmwareRevisionEntry 2 }
	 
	 rName OBJECT-TYPE
	    SYNTAX      DisplayString
	    MAX-ACCESS  read-only
	    STATUS      current
		DESCRIPTION "Name of the system element"
	    ::= { firmwareRevisionEntry 3 }
	 
	 rRevision OBJECT-TYPE
	    SYNTAX      DisplayString
	    MAX-ACCESS  read-only
	    STATUS      current
		DESCRIPTION "Firmware revision of the system element"
	    ::= { firmwareRevisionEntry 4 }
		
	 rDescription OBJECT-TYPE
	    SYNTAX      DisplayString
	    MAX-ACCESS  read-only
	    STATUS      current
		DESCRIPTION "Description of the system element"
	    ::= { firmwareRevisionEntry 5 }
	
	 rBseSse OBJECT-TYPE
		SYNTAX      DisplayString
		MAX-ACCESS  read-only
		STATUS current
		DESCRIPTION "Address of the system element"
		::= { firmwareRevisionEntry 6 }
		    
	 rHwNr OBJECT-TYPE
	    SYNTAX      DisplayString
	    MAX-ACCESS  read-only
	    STATUS      current
		DESCRIPTION "Hardware number of the system element"
	    ::= { firmwareRevisionEntry 7 }
		
	 rFwNr OBJECT-TYPE
	    SYNTAX      DisplayString
	    MAX-ACCESS  read-only
	    STATUS      current
		DESCRIPTION "Firmware number of the system element"
	    ::= { firmwareRevisionEntry 8 }		
		
    classInternal OBJECT-TYPE	
		SYNTAX  INTEGER {error(1)}
		MAX-ACCESS		read-only
		STATUS			current
		DESCRIPTION		"Are errors, that can be unequivocally traced back to system elements in the automation unit
                        (Firmware or Hardware)."
		::=  { sumDiagnosticTable  1 }

    classExternal	OBJECT-TYPE	
		SYNTAX  INTEGER {error(1)}
		MAX-ACCESS		read-only
		STATUS			current
		DESCRIPTION		"Are errors, that are detected through monitoring the information from sensors and actuators.
                         They can concern the peripheral element, the wiring and sensors or actuators, insofar as the
                         source of error can not be unequivocally localized to the peripheral element; then it would be
                         an internal error."
		::=  { sumDiagnosticTable  2 }

    classCommunication OBJECT-TYPE	
		SYNTAX  INTEGER {error(1)}
		MAX-ACCESS		read-only
		STATUS			current
		DESCRIPTION		"Are errors, that are detected by protocol elements and result from the monitoring of the
                         communication line, insofar as the source of error can not be unequivocally localized to the
                         protocol element; then it would be an internal error."
		::=  { sumDiagnosticTable  3 }

    classTest	OBJECT-TYPE	
		SYNTAX  INTEGER {error(1)}
        MAX-ACCESS		read-only
        STATUS			current
        DESCRIPTION		"Test means, that a clearly assigned function is in test; e.g. Online-Test of the Open-/Closed-
                         Loop Control Function."
        ::=  { sumDiagnosticTable  4 }

    classWarning	OBJECT-TYPE	
		SYNTAX  INTEGER {error(1)}
		MAX-ACCESS		read-only
		STATUS			current
		DESCRIPTION		"Warning indicates, that the system is still functioning, but has limited functionality or
                         availability, e.g. parameter error, poor line quality, external minute synchronization failed, but
                         internal quartz accuracy is still sufficient."
		::=  { sumDiagnosticTable  5 }

    classBoardFailure	OBJECT-TYPE	
		SYNTAX  INTEGER {error(1)}
		MAX-ACCESS		read-only
		STATUS			current
		DESCRIPTION		"Signals, that the internal communication with a system element is no longer possible 
		                 and will be created by the monitoring basic system element."
		::=  { sumDiagnosticTable  6 }

    classFailure	OBJECT-TYPE	
		SYNTAX  INTEGER {error(1)}
		MAX-ACCESS		read-only
		STATUS			current
		DESCRIPTION		"Signals, that an automation unit can no longer be reached 
		                 and will be created by the monitoring automation unit."
		::=  { sumDiagnosticTable  7 }

    classStartUp	OBJECT-TYPE	
		SYNTAX  INTEGER {error(1)}
		MAX-ACCESS		read-only
		STATUS			current
		DESCRIPTION		"Signals, that the automation unit or the system element has started up following Power-Up or
                         Reset."
		::=  { sumDiagnosticTable  8 }

    classParameter	OBJECT-TYPE	
		SYNTAX  INTEGER {error(1)}
		MAX-ACCESS		read-only
		STATUS			current
		DESCRIPTION		"Parameter error indicates, that actual device 
		                 configuration is inconsistent or invalid."
		::=  { sumDiagnosticTable  9 }

    classHWConf	OBJECT-TYPE	
		SYNTAX  INTEGER {error(1)}
		MAX-ACCESS		read-only
		STATUS			current
		DESCRIPTION		"Signals, that the device detected an internal 
		                or external hardware failure."
		::=  { sumDiagnosticTable  10 }			
			
	diagnosticEvent NOTIFICATION-TYPE
		OBJECTS     { diagnosticClass, diagnosticCondition, diagnosticDate }
		STATUS      current
		DESCRIPTION
			"SICAM RTUs sum diagnostic events inform about current state
			 of all modules of the SICAM RTU."
		::= { sumDiagnosticTraps 1 }

	diagnosticClass OBJECT-TYPE
		SYNTAX       Integer32 (1..10)
		MAX-ACCESS   accessible-for-notify
		STATUS       current
		DESCRIPTION 
			"Diagnostic Class: 1 - 10 depending on type of diagnostic event 
			 and correlating with objects of sumDiagnosticTable. 
             Class 1 is an internal error, 
             Class 2 is an external error,		
			 Class 3 is a communication error, 
             Class 4 signals that a function is in test,
			 Class 5 is a warning, 
             Class 6 is a board failure,		
			 Class 7 signals a failure of the automation unit, 
			 Class 8 signals a start up,
			 Class 9 signals a parameter failure,
			 Class 10 signals a hardware configuration failure"
		::= { sumDiagnosticTraps 2 }		

	diagnosticCondition OBJECT-TYPE
		SYNTAX       Integer32 (0..1)
		MAX-ACCESS   accessible-for-notify
		STATUS       current
		DESCRIPTION 
			"Condition: 0 = going event / 1 = coming event"
		::= { sumDiagnosticTraps 3 }	
		
	diagnosticDate OBJECT-TYPE
		SYNTAX DateAndTime
		MAX-ACCESS  read-only
		STATUS current
		DESCRIPTION
			  "The local date and time of day when event occurs."
		::= { sumDiagnosticTraps 4 }		

	trapHistoryTable OBJECT-TYPE
		SYNTAX      SEQUENCE OF TrapHistoryEntry
		MAX-ACCESS  not-accessible
		STATUS      current
		DESCRIPTION
			"List of last send SICAM RTUs traps including cold start trap,
			 link up/down traps and SICAM RTUs sum diagnostic events"
		::= { history 1 }

	trapHistoryEntry  OBJECT-TYPE
		SYNTAX      TrapHistoryEntry
		MAX-ACCESS  not-accessible
		STATUS      current
		DESCRIPTION
			 "An entry in the list of last send SICAM RTUs traps"
		INDEX       { trapHistoryIndex }
		::= { trapHistoryTable 1 }

	TrapHistoryEntry ::=
		SEQUENCE {
			trapHistoryIndex     Integer32,
			trapHistoryTrapDate  DateAndTime,			
			trapHistoryTrapOID   OBJECT IDENTIFIER,
			trapHistoryTrapState Integer32,
			trapHistoryTrapArg1  DisplayString,
			trapHistoryTrapArg2  DisplayString,			
			trapHistoryTrapArg3  DisplayString
		}		
		
	trapHistoryIndex OBJECT-TYPE
		SYNTAX      Integer32 (0..16383)
		MAX-ACCESS  read-only
		STATUS      current
		DESCRIPTION
			"Index of last send SICAM RTUs traps" 
		::= { trapHistoryEntry 1 }
	
	trapHistoryTrapDate OBJECT-TYPE
		SYNTAX DateAndTime
		MAX-ACCESS  read-only
		STATUS current
		DESCRIPTION "The local date and time of day when trap occurs."
		::= { trapHistoryEntry 2 }
	
	trapHistoryTrapOID OBJECT-TYPE
	   SYNTAX      OBJECT IDENTIFIER
	   MAX-ACCESS  read-only
	   STATUS      current
	   DESCRIPTION "The traps OID"
	   ::= { trapHistoryEntry 3 }
	   
	trapHistoryTrapState OBJECT-TYPE
	   SYNTAX      Integer32 (0..1)
	   MAX-ACCESS  read-only
	   STATUS      current
	   DESCRIPTION "The traps condition: 0 = event is going / 1 = event 
					is coming"
	   ::= { trapHistoryEntry 4 }  

	trapHistoryTrapArg1 OBJECT-TYPE
	   SYNTAX      DisplayString
	   MAX-ACCESS  read-only
	   STATUS      current
	   DESCRIPTION "An additional variable of the trap"
	   ::= { trapHistoryEntry 5 }

	trapHistoryTrapArg2 OBJECT-TYPE
	   SYNTAX      DisplayString
	   MAX-ACCESS  read-only
	   STATUS      current
	   DESCRIPTION "An additional variable of the trap"
	   ::= { trapHistoryEntry 6 }  

	trapHistoryTrapArg3 OBJECT-TYPE
	   SYNTAX      DisplayString
	   MAX-ACCESS  read-only
	   STATUS      current
	   DESCRIPTION "An additional variable of the trap"
	   ::= { trapHistoryEntry 7 }     
		
END
