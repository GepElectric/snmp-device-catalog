-- Siemens Energy Management Digital Grid Product Inventory MIB
--
-- Contact:      support.energy@siemens.com
--
-- Copyright (C) 2017 by Siemens AG, EM DG PRO D
--


DGPI-MIB DEFINITIONS ::= BEGIN

IMPORTS
    MODULE-IDENTITY, OBJECT-TYPE, NOTIFICATION-TYPE, Integer32
        FROM SNMPv2-SMI
    TEXTUAL-CONVENTION, DateAndTime
        FROM SNMPv2-TC
    MODULE-COMPLIANCE, OBJECT-GROUP, NOTIFICATION-GROUP       
        FROM SNMPv2-CONF
    SnmpAdminString
        FROM SNMP-FRAMEWORK-MIB
    siemensCommon                               
        FROM SIEMENS-SMI;


dgpiMIB MODULE-IDENTITY
    LAST-UPDATED "20170914"            
    ORGANIZATION "Siemens AG
                  Energy Management
                  Digital Grid
                  Products
                  EM DG PRO D

                  Humboldtstr. 59
                  90459 Nuremberg
                  GERMANY"
    CONTACT-INFO "support.energy@siemens.com"
    DESCRIPTION  "Inventory data of Siemens Energy Management Digital Grid 
                 products"

    ::= { siemensCommon 1 }


-- Administrative assignments

dgpiProdIdentity OBJECT IDENTIFIER  ::= { dgpiMIB 1 }
dgpiProdComp OBJECT IDENTIFIER      ::= { dgpiMIB 2 }
dgpiNotifications OBJECT IDENTIFIER ::= { dgpiMIB 3 }
dgpiConformance OBJECT IDENTIFIER   ::= { dgpiMIB 4 }


-- Textual Conventions

ProdCompIndex ::=     TEXTUAL-CONVENTION
    STATUS         current
    DESCRIPTION
         "An arbitrary value that uniquely identifies the product or component.
          The value should be a small positive integer.
          Index values for different components are not
          necessarily contiguous."
    SYNTAX       Integer32 (1..2147483647)


ProdCompIndexOrZero ::=     TEXTUAL-CONVENTION
    STATUS         current
    DESCRIPTION
         "An extension of the ProdCompIndex TEXTUAL-CONVENTION.
          This extension permits the additional value of zero.
          A value higher than zero uniquely identifies the product or 
          component. The value of zero means that no product or component 
          is referenced."
    SYNTAX       Integer32 (0..2147483647)

ProdCompClass ::=     TEXTUAL-CONVENTION
    STATUS         current
    DESCRIPTION
          "The class of the product or component.
           hwProduct:              hardware product,
           swProduct:              software product,
           mainHwComponent:        main component of hardware product,
           extensionHwComponent:   extension component of hardware product, 
                                   e.g. a plug-in module,
           updatableHwComponent:   updatable component of hardware product, 
                                   e.g. a FPGA,
           mainFwSwComponent:      main firmware component of hardware product or
                                   main software component of software product,
           extensionFwSwComponent: extension firmware component of hardware product or
                                   extension software component of software product, 
           configurationComponent: configuration of hardware or software 
                                   product or component."

    SYNTAX       INTEGER { 
                            hwProduct(1),
                            swProduct(2),
                            mainHwComponent(3),
                            extensionHwComponent(4),
                            updatableHwComponent(5),
                            mainFwSwComponent(6),
                            extensionFwSwComponent(7),
                            configurationComponent(8)
                          }

--------------------------------
-- The Product Identity Group --
--------------------------------

dgpiVendorName  OBJECT-TYPE
    SYNTAX       SnmpAdminString
    MAX-ACCESS   read-only
    STATUS       current
    DESCRIPTION "Vendor name of the product."

    ::= { dgpiProdIdentity 1 }


dgpiAssetUuid  OBJECT-TYPE
    SYNTAX       SnmpAdminString
    MAX-ACCESS   read-only
    STATUS       current
    DESCRIPTION "The Asset Universally Unique Identifier of 
                 the deployed product."

    ::= { dgpiProdIdentity 2 }


dgpiCustomerName  OBJECT-TYPE
    SYNTAX       SnmpAdminString
    MAX-ACCESS   read-only
    STATUS       current
    DESCRIPTION "The name of the customer deploying the product."

    ::= { dgpiProdIdentity 3 }


dgpiLocationName  OBJECT-TYPE
    SYNTAX       SnmpAdminString
    MAX-ACCESS   read-only
    STATUS       current
    DESCRIPTION "The location where the product is deployed."

    ::= { dgpiProdIdentity 4 }


dgpiGeoPositionLatitude  OBJECT-TYPE
    SYNTAX       SnmpAdminString
    MAX-ACCESS   read-only
    STATUS       current
    DESCRIPTION "Geographical position of the product: latitude.
                 The geodetic reference system is WGS84.
                 The preferred format is decimal grad with grad symbol 
                 and leading '+' or '-' sign."

    ::= { dgpiProdIdentity 5 }


dgpiGeoPositionLongitude  OBJECT-TYPE
    SYNTAX       SnmpAdminString
    MAX-ACCESS   read-only
    STATUS       current
    DESCRIPTION "Geographical position of the product: longitude.
                 The geodetic reference system is WGS84. 
                 The preferred format is decimal grad with grad symbol 
                 and leading '+' or '-' sign."

    ::= { dgpiProdIdentity 6 }


dgpiGeoPositionAltitude  OBJECT-TYPE
    SYNTAX       SnmpAdminString
    MAX-ACCESS   read-only
    STATUS       current
    DESCRIPTION "Geographical position of the product: altitude.
                 The geodetic reference system is WGS84.
                 The preferred format is meters with m symbol 
                 and leading '+' or '-' sign."

    ::= { dgpiProdIdentity 7 }


-----------------------------------
-- The Product & Components Group --
-----------------------------------

-- The Product & Components Table
dgpiProductComponentsTable  OBJECT-TYPE
    SYNTAX      SEQUENCE OF DgpiProdCompEntry
    MAX-ACCESS  not-accessible
    STATUS      current
    DESCRIPTION
            "This table contains one row per product and component.  
             The first row represents the product. Further rows represent
             components of this product."
    
    ::= { dgpiProdComp 1 }


dgpiProdCompEntry  OBJECT-TYPE
    SYNTAX      DgpiProdCompEntry
    MAX-ACCESS  not-accessible
    STATUS      current
    DESCRIPTION
            "Information about a particular product and its components."
    INDEX   { dgpiProdCompIndex }
    
    ::= { dgpiProductComponentsTable 1 }


DgpiProdCompEntry ::= SEQUENCE {
      dgpiProdCompIndex               ProdCompIndex,
      dgpiProdCompContainedIn         ProdCompIndexOrZero,
      dgpiProdCompClass               ProdCompClass,
      dgpiProdCompName                SnmpAdminString,
      dgpiProdCompDescription         SnmpAdminString,
      dgpiProdCompOrderNumber         SnmpAdminString,
      dgpiProdCompSerialNumber        SnmpAdminString,
      dgpiProdCompVersion             SnmpAdminString, 
      dgpiProdCompHwSlot              SnmpAdminString,
      dgpiProdCompManufactDate        DateAndTime,
      dgpiProdCompLastChange          DateAndTime
}


dgpiProdCompIndex   OBJECT-TYPE
    SYNTAX      ProdCompIndex
    MAX-ACCESS  not-accessible
    STATUS      current
    DESCRIPTION
            "The index for this entry."

    ::= { dgpiProdCompEntry 1 }


dgpiProdCompContainedIn  OBJECT-TYPE
    SYNTAX      ProdCompIndexOrZero
    MAX-ACCESS  read-only
    STATUS      current
    DESCRIPTION
            "The value of dgpiProdCompIndex for the product or component 
             that 'contains' this component.  The zero value indicates
             this item is not contained in any other item: 
             it is the product itself. 
                        
             Note that the set of 'containment' relationships
             define a strict hierarchy; that is, recursion is not
             allowed."

    ::= { dgpiProdCompEntry 2 }


dgpiProdCompClass  OBJECT-TYPE
    SYNTAX      ProdCompClass
    MAX-ACCESS  read-only
    STATUS      current
    DESCRIPTION
            "The class of the product or component which is represented by 
             this row."

    ::= { dgpiProdCompEntry 3 }


dgpiProdCompName  OBJECT-TYPE
    SYNTAX      SnmpAdminString
    MAX-ACCESS  read-only
    STATUS      current
    DESCRIPTION
            "The name of the product or component which is represented by 
             this row. If there is no name available or applicable then 
             this object contains a zero-length string."

    ::= { dgpiProdCompEntry 4 }


dgpiProdCompDescription  OBJECT-TYPE
    SYNTAX      SnmpAdminString
    MAX-ACCESS  read-only
    STATUS      current
    DESCRIPTION
            "The short description of the product or component which is 
             represented by this row. If there is no description available 
             or applicable then this object contains a zero-length string."

    ::= { dgpiProdCompEntry 5 }


dgpiProdCompOrderNumber  OBJECT-TYPE
    SYNTAX      SnmpAdminString
    MAX-ACCESS  read-only
    STATUS      current
    DESCRIPTION
            "The Siemens order number (MLFB) of this hardware or software 
             product or component. If there is no order number available or 
             applicable then this object contains a zero-length string."

    ::= { dgpiProdCompEntry 6 }


dgpiProdCompSerialNumber  OBJECT-TYPE
    SYNTAX      SnmpAdminString
    MAX-ACCESS  read-only
    STATUS      current
    DESCRIPTION
            "The serial number of this hardware product or component.
             If there is no serial number available or applicable then 
             this object contains a zero-length string."

    ::= { dgpiProdCompEntry 7 }


dgpiProdCompVersion  OBJECT-TYPE
    SYNTAX      SnmpAdminString
    MAX-ACCESS  read-only
    STATUS      current
    DESCRIPTION
            "The version of this hardware, software or configuration component.
             If there is no version available or applicable then this object 
             contains a zero-length string."

    ::= { dgpiProdCompEntry 8 }


dgpiProdCompHwSlot    OBJECT-TYPE
    SYNTAX      SnmpAdminString
    MAX-ACCESS  read-only
    STATUS      current
    DESCRIPTION
            "The slot identifier of the 'parent' hardware product's or 
             component's slot which is occupied by this 'child' hardware 
             component. If there is no slot identifier available or applicable
             then this object contains a zero-length string."

    ::= { dgpiProdCompEntry 9 }


dgpiProdCompManufactDate    OBJECT-TYPE
    SYNTAX      DateAndTime
    MAX-ACCESS  read-only
    STATUS      current
    DESCRIPTION
            "The manufacturing date of the hardware product or component.
             If there is no manufacturing date available or applicable then 
             this object contains the special value '0000000000000000'H."

    ::= { dgpiProdCompEntry 10 }


dgpiProdCompLastChange    OBJECT-TYPE
    SYNTAX      DateAndTime
    MAX-ACCESS  read-only
    STATUS      current
    DESCRIPTION
            "The component's last change date and time. 
             If there is no change date and time available 
             or applicable then this object contains the 
             special value '0000000000000000'H."

    ::= { dgpiProdCompEntry 11 }


-- The Product & Components Table's last change
dgpiProdCompTableLastChange    OBJECT-TYPE
    SYNTAX      DateAndTime
    MAX-ACCESS  read-only
    STATUS      current
    DESCRIPTION
            "The Product & Components Table's last change date and time. 
             The change includes creation of an additional row, 
             deletion of a previously existing row and modification of 
             an existing row."
 
    ::= { dgpiProdComp 2 }


-----------------------------
-- The Notifications Group --
-----------------------------

dgpiNotificationsEnabled       OBJECT-TYPE
    SYNTAX       INTEGER { no(1), yes(2) }
    MAX-ACCESS   read-write
    STATUS       current
    DESCRIPTION
            "Determines whether the SNMP agent is permitted to generate 
             dgpi notifications."

    ::= { dgpiNotifications 1 }


dgpiNotificationProdCompChanged   NOTIFICATION-TYPE
    OBJECTS      { dgpiProdCompTableLastChange }
    STATUS       current
    DESCRIPTION
            "This notification identifies that the 
             dgpiProductComponentsTable has changed.
             This notification is sent if dgpiNotificationsEnabled is set 
             to yes and the value of dgpiProdCompTableLastChange has changed."

    ::= { dgpiNotifications 2 }


-----------------------------
-- Conformance Information --
-----------------------------

dgpiCompliances OBJECT IDENTIFIER ::= { dgpiConformance 1 }
dgpiGroups      OBJECT IDENTIFIER ::= { dgpiConformance 2 }

-- Compliance statements

dgpiCompliance MODULE-COMPLIANCE
    STATUS       current
    DESCRIPTION "The compliance statement for SNMP engines which
                 implement the DGPI-MIB."

    MODULE       -- this module
        MANDATORY-GROUPS { dgpiProductIdentityGroup,
                           dgpiProdCompGroup
                         }

    ::= { dgpiCompliances 1 }

-- Units of compliance

dgpiProductIdentityGroup OBJECT-GROUP
    OBJECTS     {
                  dgpiVendorName,
                  dgpiAssetUuid,
                  dgpiCustomerName,
                  dgpiLocationName,
                  dgpiGeoPositionLatitude,
                  dgpiGeoPositionLongitude,
                  dgpiGeoPositionAltitude
                }
    STATUS       current
    DESCRIPTION "This group provides basic information about the product.
                 The implementation of this group is mandatory."
    ::= { dgpiGroups 1 }


dgpiProdCompGroup OBJECT-GROUP
    OBJECTS     { 
                  dgpiProductComponentsTable,
                  dgpiProdCompEntry,
                  dgpiProdCompIndex,
                  dgpiProdCompContainedIn,
                  dgpiProdCompClass,
                  dgpiProdCompName,
                  dgpiProdCompDescription,
                  dgpiProdCompOrderNumber,
                  dgpiProdCompSerialNumber,
                  dgpiProdCompVersion,
                  dgpiProdCompHwSlot,
                  dgpiProdCompManufactDate,
                  dgpiProdCompLastChange,
                  dgpiProdCompTableLastChange
                }
    STATUS       current
    DESCRIPTION "This group provides detailed information about the product
                 and its components. The implementation of this group is 
                 mandatory."
    ::= { dgpiGroups 2 }


dgpiNotifObjectsGroup OBJECT-GROUP
    OBJECTS     { 
                  dgpiNotificationsEnabled
                }
    STATUS       current
    DESCRIPTION "This group contains objects for product or 
                 component related notifications. The implementation of 
                 this group is optional."
    ::= { dgpiGroups 3 }


dgpiNotifNotificationsGroup NOTIFICATION-GROUP
    NOTIFICATIONS { 
                    dgpiNotificationProdCompChanged
                  }
    STATUS       current
    DESCRIPTION "This group contains product or component related 
                 notifications. The implementation of this group
                 is optional."
    ::= { dgpiGroups 4 }


END
