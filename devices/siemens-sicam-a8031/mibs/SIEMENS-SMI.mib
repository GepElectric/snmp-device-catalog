SIEMENS-SMI DEFINITIONS ::= BEGIN

IMPORTS
    MODULE-IDENTITY, OBJECT-IDENTITY, enterprises
        FROM SNMPv2-SMI;

siemens MODULE-IDENTITY
    LAST-UPDATED "201708230913Z"
    ORGANIZATION "Siemens"
    CONTACT-INFO
            "        Siemens
		     E-mail: support.ic@siemens.com"
    DESCRIPTION
            "The Structure of Management Information for Siemens."
    ::= { enterprises 22638 }

sicamRTUs OBJECT-IDENTITY
    STATUS  current
    DESCRIPTION
            "The root of SICAM 1703 device OIDs."
    ::= { siemens 7 }

siemensCommon OBJECT-IDENTITY
    STATUS  current
    DESCRIPTION
            "The root of common OIDs."
    ::= { siemens 11 }	
	
END
